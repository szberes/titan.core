--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test303A

DEFINITIONS

::=

BEGIN

IMPORTS ; -- nothing

MyBitstringType1 ::= BIT STRING { first(0), other (5) }

myBitstringValue1 MyBitstringType1 ::=
 {first, other } --'100001'B

myGeneralStringValue1 GeneralString ::= "General"

END
