--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test309A
DEFINITIONS

AUTOMATIC TAGS

::=

BEGIN

MyIA5StringType1 ::= IA5String

myIA5StringValue1 MyIA5StringType1 ::=
"~!@#$%^%&^*()_+`""HAHO"" 1234567890-=qwertyuiop[]\QWERTYUIOP{}|asdfghjkl;'ASDFGHJKL:zxcvbnm,./ZXCVBNM<>?"

END
