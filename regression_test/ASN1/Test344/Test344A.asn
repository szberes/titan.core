--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test344A
DEFINITIONS

AUTOMATIC TAGS

::=

BEGIN

MyObjectIdentifierType1 ::= OBJECT IDENTIFIER

myObjectIdentifierValue1 MyObjectIdentifierType1 ::= {abrax(0) brabax(3) califax(7)}

END
