--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test356A
DEFINITIONS

AUTOMATIC TAGS

::=

BEGIN

IMPORTS ; -- nothing

MySequenceType2 ::= SEQUENCE {
  			     field1 INTEGER,
			     field2 BOOLEAN,
			    -- field3 NULL,
			     field4 OCTET STRING,
			     field5 BIT STRING,
			     field6 ENUMERATED {a1,b1,c1}
			   --  field7 REAL   NOT SUPP
			    }



MySetType2 ::= SET{
  			     field1 INTEGER,
			     field2 BOOLEAN,
			    -- field3 NULL,
			     field4 OCTET STRING,
			     field5 BIT STRING,
			     field6 ENUMERATED {a2,b2,c2}
			    -- field7 REAL   NOT SUPP
			    }
MyChoiceType2 ::= CHOICE{
  			     field1 INTEGER,
			     field2 BOOLEAN,
			   --  field3 NULL,
			     field4 OCTET STRING,
			     field5 BIT STRING,
			     field6 ENUMERATED {a3,b3,c3}
			    --  field7 REAL NOT SUPP
			    }






MySetOfType1 ::= SET OF INTEGER

mySetOfValue1A MySetOfType1 ::= {3,664,234,-1 ,0}

MySetOfType2 ::= SET OF BIT STRING

mySetOfValue2A MySetOfType2 ::= {'0011'B, '1'B, '00'B}

MySetOfType3 ::= SET OF OCTET STRING

mySetOfValue3A MySetOfType3 ::= {'FFAA'H, '1234'H, '00'H}

MySetOfType4 ::= SET OF BOOLEAN

mySetOfValue4A MySetOfType4 ::= {TRUE, FALSE, TRUE}

MySetOfType5 ::= SET OF MySequenceType2

mySetOfValue5A MySetOfType5 ::=
 {
     {
     field1   5,
     field2   TRUE,
     field4   '1234567890FF'H,
     field5   '10'B,
     field6    a1
      },

       {
       field1   77,
       field2   FALSE,
       field4    '1234AA'H,
       field5    '01'B,
       field6    c1
       }

  }


MySetOfType6 ::= SET OF MySetType2

mySetOfValue6A MySetOfType6 ::=
 {
     {
     field1   5,
     field4   '1234567890FF'H,
     field2   TRUE,
     field5   '10'B,
     field6    a2
      },

       {
       field5    '01'B,
       field1   77,
       field2   FALSE,
       field4    '1234AA'H,
       field6    c2
       }

  }



 MySetOfType7 ::= SET OF MyChoiceType2

mySetOfValue7A MySetOfType7 ::=
  {

       field1  :  5
       ,


       field2  :  FALSE

  }


END
