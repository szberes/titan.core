--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test52
DEFINITIONS

AUTOMATIC TAGS

::=

BEGIN


IMPORTS ; -- nothing

MyBitstringType ::= BIT STRING

myBitstringValue1 MyBitstringType ::=  '1234567890ABCDEF'H

myBitstringValue2 BIT STRING ::= 'ABCDEF1234567890'H


END
