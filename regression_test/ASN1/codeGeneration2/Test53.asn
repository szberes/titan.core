--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test53
DEFINITIONS

AUTOMATIC TAGS

::=

BEGIN


IMPORTS ; -- nothing

MyBitstringType ::= BIT STRING { first(0), second (1), last-in-first-octet(7) }

myBitstringValue1 MyBitstringType ::= {first, last-in-first-octet }

myBitstringValue2 BIT STRING { apple(0),  orange(1), cherry(7) }::= {orange, apple}


END
