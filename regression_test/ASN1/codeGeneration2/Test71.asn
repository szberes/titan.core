--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test71

DEFINITIONS

AUTOMATIC TAGS

::=

BEGIN

IMPORTS ; -- nothing

MyChoiceType1 ::= CHOICE
			    {
  			     field1 INTEGER,
			     field2 BOOLEAN,
			     field3 NULL,
			     field4 OCTET STRING,
			     field5 BIT STRING,
			     field6 ENUMERATED {a,b,c},
			     field7 REAL
			    }

MySelectionType1 ::= field1 < MyChoiceType1

mySelectionValue1 MySelectionType1 ::= 123

MySelectionType2 ::= field2 < MyChoiceType1

mySelectionValue2 MySelectionType2 ::= TRUE

MySelectionType3 ::= field3 < MyChoiceType1

mySelectionValue3 MySelectionType3 ::= NULL

MySelectionType4 ::= field4 < MyChoiceType1

mySelectionValue4 MySelectionType4 ::= '1234567890ABCDEF'H

MySelectionType5 ::= field5 < MyChoiceType1

mySelectionValue5 MySelectionType5 ::= ''B

MySelectionType6 ::= field6 < MyChoiceType1

mySelectionValue6 MySelectionType6 ::= b

MySelectionType7 ::= field7 < MyChoiceType1

mySelectionValue7 MySelectionType7 ::= 0






END
