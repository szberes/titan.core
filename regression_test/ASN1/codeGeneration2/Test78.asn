--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test78

DEFINITIONS

AUTOMATIC TAGS

::=

BEGIN

IMPORTS ; -- nothing

MySequenceType1 ::= SEQUENCE {
  			     field1 INTEGER,
			     field2 BOOLEAN,
			     field3 NULL,
			     field4 OCTET STRING,
			     field5 BIT STRING,
			     field6 ENUMERATED {a,b,c},
			     field7 REAL
			    }


mySequenceValue1 MySequenceType1 ::=  {
  			     field1 555,                    -- INTEGER,
			     field2 TRUE,                   -- BOOLEAN,
			     field3 NULL,
			     field4 'FF00'H,                 -- OCTET STRING,
			     field5 '01010'B,                -- BIT STRING,
			     field6  a,                      --ENUMERATED {a,b,c},
			     field7  5.2 -- {mantissa 10,base 2, exponent 2} --  --REAL
			    }

END
