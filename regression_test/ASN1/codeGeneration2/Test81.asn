--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test81

DEFINITIONS

AUTOMATIC TAGS

::=

BEGIN

IMPORTS ; -- nothing

MySequenceType1 ::= SEQUENCE {
  			     field1 INTEGER DEFAULT 8,
			     field2 BOOLEAN DEFAULT TRUE,
			     field3 NULL DEFAULT NULL,
			     field4 OCTET STRING DEFAULT 'FFFF'H,
			     field5 BIT STRING DEFAULT '01010'B,
			     field6 ENUMERATED {a,b,c},
			     field7 REAL
			    }


mySequenceValue1 MySequenceType1 ::=
			{    field5 '11'B,
  			     field6  a,   --ENUMERATED {a,b,c},
			     field7  5.2 -- {mantissa 10,base 2, exponent 2} --  --REAL
			}

END
