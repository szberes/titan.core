--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test83

DEFINITIONS

AUTOMATIC TAGS

::=

BEGIN

IMPORTS ; -- nothing

MySequenceType1 ::= SEQUENCE {
  			     field1 INTEGER,
			     field2 BOOLEAN,
			     field3 NULL,
			     field4 OCTET STRING,
			     field5 BIT STRING,
			     field6 ENUMERATED {a,b,c},
			     field7 REAL
			    }


MySetType1 ::= SET {
  			     field1 INTEGER,
			     field2 BOOLEAN  OPTIONAL,
			     field3 NULL,
			     field4 OCTET STRING,
			     field5 BIT STRING,
			     field6 ENUMERATED {a,b,c},
			     field7 REAL OPTIONAL,
			     field8 MySequenceType1
			    }

mySetValue1 MySetType1 ::=  {
  			     field1 555,               -- INTEGER,
			     field2 TRUE,              -- BOOLEAN,
			     field3 NULL,
			     field4 'FF00'H,           -- OCTET STRING,
			     field5 '01010'B,          -- BIT STRING,
			     field6  a,                --ENUMERATED {a,b,c),
			     field7  5.2, -- {mantissa 10,base 2, exponent 2}, -- --REAL
			     field8  {
			               field1  1,
				       field2  TRUE,
				       field3  NULL,
				       field4  '0'H,
				       field5  '0'B,
				       field6   b,
				       field7 5.2 -- {mantissa 10,base 2, exponent 2}
				     }

			 }

mySetValue2 MySetType1 ::=  {

			     field3 NULL,
			     field4 'FF00'H,           -- OCTET STRING,
			     field5 '01010'B,          -- BIT STRING,
			     field7  5.2, -- {mantissa 10,base 2, exponent 2}, -- --REAL
			     field8  {
			               field1  1,
				       field2  TRUE,
				       field3  NULL,
				       field4  '0'H,
				       field5  '0'B,
				       field6   b,
				       field7 5.2 -- {mantissa 10,base 2, exponent 2}
				     },
			     field6  a,                --ENUMERATED {a,b,c),
			     field1 555               -- INTEGER,
			     }



END
