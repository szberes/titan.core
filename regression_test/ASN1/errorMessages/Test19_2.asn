--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test19-2
DEFINITIONS

AUTOMATIC TAGS

::=

BEGIN

MyBitstringType2 ::= BIT STRING{ first(0), second (-1), last-in-first-octet(7) }

END
