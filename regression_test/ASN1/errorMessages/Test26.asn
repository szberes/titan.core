--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test26
DEFINITIONS

IMPLICIT TAGS

::=

BEGIN

MyChoiceType ::= CHOICE
			    {
  			     field1 [0] INTEGER,
			     field2 [1] BOOLEAN,
			     field3 [2] NULL,
			     field4 [3] OCTET STRING,
			     field5 [3] BIT STRING,
			     field6 [5] ENUMERATED {a,b,c},
			     field7 [6] REAL
			    }

END
