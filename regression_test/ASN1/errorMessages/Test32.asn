--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test32
DEFINITIONS

IMPLICIT TAGS

::=

BEGIN

MySequenceType ::= SEQUENCE {
  			     field1  INTEGER,
			     field2 [0] BOOLEAN OPTIONAL,
			     field3 [0] NULL OPTIONAL,
			     field4 [1] OCTET STRING OPTIONAL,
			     field5 [2] BIT STRING ,
			     field6 [3] ENUMERATED {a,b,c} OPTIONAL,
			     field7 [4] REAL
			    }

END
