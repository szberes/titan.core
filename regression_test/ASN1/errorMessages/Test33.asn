--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test33
DEFINITIONS

IMPLICIT TAGS

::=

BEGIN

MySequenceType ::= SEQUENCE {
  			     field1  INTEGER,
			     field2 [0] BOOLEAN DEFAULT TRUE,
			     field3 [5] NULL OPTIONAL,
			     field4 [0] OCTET STRING DEFAULT 'FFFF'H,
			     field5 [2] BIT STRING ,
			     field6 [3] ENUMERATED {a,b,c} OPTIONAL,
			     field7 [4] REAL
			    }

END
