--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test67

DEFINITIONS

AUTOMATIC TAGS

::=

BEGIN

MyEnumeratedType1 ::= ENUMERATED {a(0),b(1),..., c(2)}

myEnumearetedValue1 MyEnumeratedType1 ::= my-nonexistent-value

END
