--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test70

DEFINITIONS

AUTOMATIC TAGS

::=

BEGIN

MyChoiceType1 ::= CHOICE
			    {
  			     field1 INTEGER,
			     field2 BOOLEAN,
			     field3 NULL,
			     field4 OCTET STRING,
			     field5 BIT STRING,
			     field6 ENUMERATED {a,b,c},
			     field7 REAL
			    }

myInvalidChoiceValue1  MyChoiceType1 ::= field8 : 5

END
