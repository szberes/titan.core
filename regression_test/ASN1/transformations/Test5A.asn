--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test5A -- extensibility implied A
DEFINITIONS

AUTOMATIC TAGS
EXTENSIBILITY IMPLIED

::=

BEGIN

IMPORTS ; -- nothing

MySequenceType1 ::= SEQUENCE
		{
		field1 INTEGER,
		field2 BOOLEAN
		}

MySetType1 ::= SET
		{
		field1 INTEGER,
		field2 BOOLEAN
		}

MyEnumeratedType ::= ENUMERATED
		{
			option1,
			option2
		}

MyChoiceType ::= CHOICE
		{
		field1 INTEGER,
		field2 BOOLEAN
		}



END
