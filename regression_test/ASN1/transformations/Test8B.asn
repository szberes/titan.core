--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Test8B --  B
DEFINITIONS

IMPLICIT TAGS


::=

BEGIN

IMPORTS ; -- nothing

MySequenceType1 ::= SEQUENCE
		{
		field1 [0] INTEGER OPTIONAL,
		field2 [1] BOOLEAN OPTIONAL,
		field3 [2] EXPLICIT CHOICE {
				f1 [0] OCTET STRING,
				f2 [1] BIT STRING
			       		   }
		}

MySetType1 ::= SET
		{
		field1 [0] INTEGER OPTIONAL,
		field2 [1] BOOLEAN OPTIONAL,
		field3 [2] EXPLICIT CHOICE {
				f1 [0] OCTET STRING,
				f2 [1] BIT STRING
			       }
		}


MySequenceType2 ::= SEQUENCE
		{
		field1 [0] INTEGER OPTIONAL,
		field2 [1] BOOLEAN OPTIONAL,
		field3 [2] EXPLICIT MyChoiceType
		}

MySetType2 ::= SET
		{
		field1 [0]INTEGER OPTIONAL,
		field2 [1] BOOLEAN OPTIONAL,
		field3 [2] EXPLICIT MyChoiceType
		}



MyChoiceType ::= CHOICE
		{
		field1 [0] INTEGER,
		field2 [1] BOOLEAN
		}




END
