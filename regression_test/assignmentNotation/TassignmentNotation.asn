--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
ASN-Definitions DEFINITIONS AUTOMATIC TAGS ::=
BEGIN
IMPORTS ; -- nothing

ASN-CSTR ::= CHARACTER STRING
ASN-SEQ-I ::= SEQUENCE (SIZE (1..10)) OF INTEGER
ASN-SEQ-R ::= SEQUENCE { asn-seq-i ASN-SEQ-I }

idx-ASN INTEGER ::= 0

END
