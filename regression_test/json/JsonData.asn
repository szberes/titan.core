--*****************************************************************************
-- Copyright (c) 2000-2014 Ericsson Telecom AB
-- All rights reserved. This program and the accompanying materials
-- are made available under the terms of the Eclipse Public License v1.0
-- which accompanies this distribution, and is available at
-- http://www.eclipse.org/legal/epl-v10.html
--*****************************************************************************
JsonData
DEFINITIONS

AUTOMATIC TAGS

::=

BEGIN

IMPORTS ;

-- Type definitions --
----------------------

SeqOfInt ::= SEQUENCE OF INTEGER

SeqProduct ::= SEQUENCE {
  name UniversalString,
  price REAL,
  id OCTET STRING OPTIONAL,
  available BOOLEAN
}

Number ::= CHOICE {
  decimal INTEGER,
  binary BIT STRING,
  hexadecimal OCTET STRING
}

AnyString ::= CHOICE {
  generalstr GeneralString,
  numericstr NumericString,
  utf8str UTF8String,
  printablestr PrintableString,
  universalstr UniversalString,
  bmpstr BMPString,
  graphicstr GraphicString,
  ia5str IA5String,
  teletexstr TeletexString,
  videotexstr VideotexString,
  visiblestr VisibleString
}

ManyStrings ::= SEQUENCE OF AnyString

ComplexSet ::= SET {
  product SeqProduct,
  numbers SET OF Number,
  strings ManyStrings
}

-- Values and their encoding --
-------------------------------

-- SeqOfInt
c-ints SeqOfInt ::= { 1, 3, 6 }

c-ints-str VisibleString ::= "[1,3,6]"

-- SeqProduct
c-product SeqProduct ::= {
  name "TV",
  price 250.0,
  id '1D65'H,
  available TRUE
}

c-product-str VisibleString ::= "{""name"":""TV"",""price"":250.000000,""id"":""1D65"",""available"":true}"

-- Number
c-number Number ::= binary : '1100'B

c-number-str VisibleString ::= "{""binary"":""1100""}"

-- ManyStrings
c-strings ManyStrings ::= {
  generalstr : "General String <o",
  numericstr : "1 457 664",
  utf8str : "Doesn't actually contain non-ASCII characters",
  printablestr : "hello",
  universalstr : "not so universal, apparently",
  bmpstr : "abc",
  ia5str : "one two three",
  teletexstr : "Let's just bug out and call it even, OK?!",
  videotexstr : "abc123;.",
  visiblestr : "invisible"
}

c-strings-str VisibleString ::= "[{""generalstr"":""General String <o""},{""numericstr"":""1 457 664""},{""utf8str"":""Doesn't actually contain non-ASCII characters""},{""printablestr"":""hello""},{""universalstr"":""not so universal, apparently""},{""bmpstr"":""abc""},{""ia5str"":""one two three""},{""teletexstr"":""Let's just bug out and call it even, OK?!""},{""videotexstr"":""abc123;.""},{""visiblestr"":""invisible""}]"

-- ComplexSet
c-set-val ComplexSet ::= {
  product {
    name "Headset",
    price 28.5,
    available FALSE
  },
  numbers {
    hexadecimal : '16678D'H,
    decimal : 12
  },
  strings {
    printablestr : "first",
    numericstr : "2"
  }
}

c-set-val-str VisibleString ::= "{""product"":{""name"":""Headset"",""price"":28.500000,""available"":false},""numbers"":[{""hexadecimal"":""16678D""},{""decimal"":12}],""strings"":[{""printablestr"":""first""},{""numericstr"":""2""}]}"

END
