--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
LazyASNTypes {1 2 3} DEFINITIONS AUTOMATIC TAGS ::=

	
	BEGIN 
		IMPORTS ;
	 	MyASNRecord ::= SEQUENCE 
	 	{
	 	  b BOOLEAN,
	 	  i INTEGER,
	 	  r REAL,
	 	  bs BIT STRING,
	 	  os OCTET STRING,
	 	  cs PrintableString
	 	} 
	 	
	 	StoreLocation ::= ENUMERATED
	    {
	         baltimore (0),
	         philadelphia (1),
	         washington (2)
        }

		MyASNUnion ::= CHOICE 
		{
		  i INTEGER,
	 	  r REAL,
	 	  cs CHARACTER STRING
		} 	
		
		myASNrec MyASNRecord ::=
		{
		  b TRUE,
		  i 1,
		  r 1.0,
		  bs '1'B,
		  os '55'H,
		  cs "a"
		}
	END
