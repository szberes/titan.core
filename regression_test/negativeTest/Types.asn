--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Types
DEFINITIONS
::=
BEGIN
IMPORTS ;

-- MyInt ::= INTEGER (1..10)

MySeq ::= SEQUENCE {
  i INTEGER,
  b BOOLEAN
}

MySeqModified ::= SEQUENCE {
  i INTEGER OPTIONAL,
  b BOOLEAN OPTIONAL
}

MySeqModified2 ::= SEQUENCE {
  bs BIT STRING,
  i INTEGER OPTIONAL,
  oc OCTET STRING,
  b BOOLEAN OPTIONAL,
  r REAL 
}

MySeqModified3 ::= SEQUENCE {
  b BOOLEAN
}

MySeqModified4 ::= SEQUENCE { 
}

MySeqModified5 ::= SEQUENCE {
  sof MySeqOf
}

MySeqModified6 ::= SEQUENCE {
  u MyUnion
}

MySeqOf ::= SEQUENCE OF INTEGER
MySeqOfModified ::= SEQUENCE OF REAL
MySeqOfModified2 ::= SEQUENCE OF BOOLEAN

MyUnion ::= CHOICE {
  i INTEGER,
  b BOOLEAN,
  s MySeq
}

MyUnionModified ::= CHOICE {
  i INTEGER,
  b BOOLEAN,
  s MySeqModified4,
  r REAL,
  bs BIT STRING,
  os OCTET STRING
}

MySeqModifiedT ::= SEQUENCE {
  b BOOLEAN,
  i INTEGER
}

MyInt ::= [77] INTEGER
MyBool::= [88] BOOLEAN

MySeqTerr ::= SEQUENCE {
  i MyInt,
  b MyBool
}

MyRecursiveSeq ::= SEQUENCE {
  r MyRecursiveSeq OPTIONAL
}

END
