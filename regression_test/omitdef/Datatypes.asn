--/////////////////////////////////////////////////////////////////////////////
-- Copyright (c) 2000-2014 Ericsson Telecom AB
-- All rights reserved. This program and the accompanying materials
-- are made available under the terms of the Eclipse Public License v1.0
-- which accompanies this distribution, and is available at
-- http://www.eclipse.org/legal/epl-v10.html
--/////////////////////////////////////////////////////////////////////////////
Datatypes DEFINITIONS AUTOMATIC TAGS
::= BEGIN

IMPORTS ;

Deff ::= SEQUENCE {
    field1 INTEGER,
    field2 INTEGER DEFAULT 13,
    field3 INTEGER
}

Opt ::= SEQUENCE {
    field1 INTEGER,
    field2 INTEGER OPTIONAL,
    field3 INTEGER
}

END
